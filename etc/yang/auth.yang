module auth {
  description "Authentication details";
  prefix "";
  namespace "";
  revision 0;

  grouping auth {

    container auth {

      container rbac {

        list role {

          key "id";

          leaf id {
            type string;
          }

          list access {

            leaf path {
              type string;
            }

            leaf-list permissions {
              type enumeration {
                enum r;
                enum w;
                enum x;
                enum s;
              }
            }
          }
        }
      }
    }
  }
}
