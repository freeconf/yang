module x {
    prefix "";
    namespace "";
    description "i am x";
    include one;
    revision 0;
    include two {
        revision 0;
        description "d";
        reference "99";
    }

    leaf x {
        type string;
    }
}
