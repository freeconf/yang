module leaf {
	namespace "";
	prefix "";
	revision 0;

    leaf l1 {
        type string;
    }

    leaf l2 {
        config false;
        mandatory true;
        description "d3";
        reference "r";   
        units english;     
        type string {
            pattern '[a-z]*';
            pattern '^(([0-9]|[1-9][0-9]|1[0-9][0-9]|2[0-4][0-9]|'  +
              '25[0-5])\.){3}([0-9]|[1-9][0-9]|1[0-9][0-9]|2[0-4]'  +
              '[0-9]|25[0-5])$';
        }
        default "foo";
    }

    leaf l3 {
        type decimal64 {
            fraction-digits 10;
            range "-99.99..99.99";
        }
    }

    leaf l4 {
        type string {
            pattern 'abc' {
                modifier invert-match;
                error-message "Text here";
            }
        }
    }
}
