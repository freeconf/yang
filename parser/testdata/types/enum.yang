module enum {
	namespace "";
    prefix "";

    leaf y {
        type enumeration {
            enum a;
            enum b {
                value 99;
            }
            enum 1k;
        }
        default 1k;
    }
}
