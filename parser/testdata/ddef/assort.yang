module assort {
    
    revision 0;

    list a {
        ordered-by user;
        leaf-list b {
            type string;
            ordered-by system;
        }
    }

    leaf ref {
        type leafref {
            path "/a/b";
            require-instance true;
        }
    }
    leaf e {
        type enumeration {
            enum x {
                value "1";
            }
        }
    }
    leaf m {
        type string;
        must '. != "true" or ../agent-id' {
            description "x";
            error-message "boo";
            error-app-tag "hello";
        }
    }

    choice c {
        description "here";
        leaf x {
            type string {
                pattern "abc.*123" {
                    description "d1";
                    error-message "em1";
                    error-app-tag "eat1";                
                }
                length 10 {
                    description "d3";
                    error-message "em3";
                    error-app-tag "eat3";                
                }
            }
        }
        leaf y {
            type int32 {
                range "13..99" {
                    description "d2";
                    error-message "em2";
                    error-app-tag "eat2";      
                } 
            }
        }
    }
    leaf b {
        type bits {
            bit b1 {
                description ".";
            }
            bit b2;
            bit b3 {
                position 10;
            }
        }
    }
}
