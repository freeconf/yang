module choice-x {

    // choice with ununusual things
    
    container x {
        choice how {
            config false;
            case one {
                leaf y {
                    type uint16;
                }
            }
            case two {
                leaf z {
                    type string;
                }
            }
        }
    }

    container y {
        choice boogie {
            case one {
                leaf y {
                    type string;
                    config true;
                }
            }
            case two {
                leaf z {
                    type string;
                }
            }
        }
    }
}
