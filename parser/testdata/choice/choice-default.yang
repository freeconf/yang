module choice-default {
    container transfer {
        choice how {
            default interval;

            case interval {
                leaf interval {
                    type uint16;
                    units minutes;
                    default 30;
                }
            }
            case daily {
                leaf daily {
                    type empty;
                }
                leaf time-of-day {
                    type string;
                    units 24-hour-clock;
                    default "01.00";
                }
            }
            case manual {
                leaf manual {
                    type empty;
                }
            }
        }
    }
}
