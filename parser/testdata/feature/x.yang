module x {
    revision 0;

    feature blacklisted;

    feature x;

    feature z {
        description "d";
    }

    leaf l1 {
        if-feature x;
        type string;
    }

    container l2 {
        if-feature "x or z";

        leaf l2 {
            if-feature x;
            if-feature z;
            type string;
        }
    }

    leaf l3 {
        type enumeration {
            enum one {
                if-feature "x";
            }
            enum two;
        }
    }

    uses g {
        if-feature blacklisted;
    }

    grouping g {
        leaf l3 {
            type string;
        }
    }
}
