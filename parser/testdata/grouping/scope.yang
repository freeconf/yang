module scope {
    prefix "";
    namespace "";
    revision 0;

    container x {
        grouping g {
            leaf z {
                type string;
            }
        }
        container y {
            uses g;
        }
    }
}
