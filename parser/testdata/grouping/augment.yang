module augment {
    namespace "";
    prefix "";
    revision 0;
    
    grouping x {
        leaf s {
            type string;
        }
        container z {
            leaf g {
                type string;
            }
        }
    }

    container t {  // should be left alone
        leaf u {
            type string;
        }
    }

    container a {
        /*
          leaf s         <- from uses
          container z    <- from uses
             leag g      <- from uses
             leaf p      <- inserted
        */
        uses x {
            augment z {
                leaf p {
                    type string;
                }
            }
        }
    }
}
