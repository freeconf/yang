module x {
    prefix "x";
    extension ext {
        description "x";
        argument "g";
    }

    extension ext2 {
    }

    description "x" {
        /* 
          all extension references require "prefix:name" format even 
          when extention is defined in local module.
        */
        x:ext 5;
    }

    leaf x {
        type string;
    }

    x:ext "a";
}
