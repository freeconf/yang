module x {
    yang-version "1.1";
    prefix "";
    namespace "";

    import one {
        prefix one;
    }
    revision "0";
    import two {
        prefix "two";
        revision 0;
        description "d";
        reference "99";
        revision-date 2023-04-06;
    }

    leaf x {
        type string;
    }

    uses one:g;
    uses two:g;
}
