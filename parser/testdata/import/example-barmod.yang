module example-barmod {

    namespace "http://example.com/barmod";

    prefix "barmod";

    import example-foomod {
        prefix "foomod";
    }

    uses foomod:x;

    augment /top {
        leaf bar {
            type boolean;
        }
    }
}
