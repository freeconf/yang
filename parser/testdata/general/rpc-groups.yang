module x {
    description "test case discovered a bug with groups
      in rpcs that incorrectly thought were recursive.";
    revision 0;

    grouping g1 {
        uses g2;
        leaf l1 {
            type string;
        }
    }

    grouping g2 {
        leaf l2 {
            type string;
        }
    }

    rpc r1 {
        input {
            uses g1;
        }
    }

    rpc r2 {
        input {
            uses g1;
        }
    }
}
