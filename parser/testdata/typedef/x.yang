module x {
    namespace "";
    prefix "";
    revision 0;

    typedef t {
        type string;
        units farming;
        default "hi";
    }

    typedef te {
        type enumeration {
            enum a;
            enum b;
        }
    }

    leaf x {
        type t;
    }

    notification n {
        leaf xe {
            type te;
        }
    }
}
