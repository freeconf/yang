module x {
    prefix "z";
    namespace "";
    revision 0;

    feature blacklisted;

    container x {
        container y {
            leaf a {
                type string;
            }
        }
    }

    augment "z:x/z:y" {
        description "x";
        leaf b {
            type string;
        }
    }

    container a {
        if-feature blacklisted;
        leaf b {
            type int32;
        }
    }

    augment a {
        if-feature blacklisted;
        leaf c {
            type int32;
        }
    }
}
