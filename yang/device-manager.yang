module device-manager {
    prefix "";
    namespace "";
    revision 0;

    grouping deviceItem {
        leaf deviceId {
            type string;
        }

        leaf address {
            type string;
        }

        list module {
            key "name";        

            leaf name {
                type string;
            }

            leaf revision {
                type string;
            }        
        }
    }

    list device {
        key "deviceId";
        config "false";
        uses deviceItem;
    }

    rpc register {
        input {
            leaf deviceId {
                description "Id that is unique to this device in the infrastructure pool";
                type string;
                mandatory "true";
            }
            leaf address {
                description  "Optional.  Will use incoming address of request.  Hint: If you use the text
                  phrase '{REG_ADD}' anywhere in the address, it will be replaced by the IP address found
                  in the registration request. This does not include the port number because often that
                  is not typically the port used when registering.  Example  https://{REG_ADDR}:8090/restconf";

                type string;
                mandatory "true";
            }
        }
    }    

    notification update {
        uses deviceItem;

        leaf change {
            type enumeration {
                enum added;
                enum removed;
            }                
        }        
    }
}
