module call-home-register {
    prefix "";
    namespace "";
    revision 0;

    rpc register {
        input {
            leaf id {
                description "Id that is unique to this device in the infrastructure pool";
                type string;
            }
            leaf address {
                description  "Optional.  Will use incoming address of request";
                type string;
            }
            leaf port {
                description  "Port number to go with address.";
                type string;
                default "443";
            }
        }
    }
}
