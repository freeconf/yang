module map {
    prefix "";
    namespace "";
    description "";
    revision 0;

    grouping deviceItem {
        leaf deviceId {
            type string;
        }

        list module {
            key "name";        

            leaf name {
                type string;
            }

            leaf revision {
                type string;
            }        
        }
    }

    list device {
        key "deviceId";
        config false;
        uses deviceItem;
    }

    rpc register {
        input {
            leaf deviceId {
                description "Id that is unique to this device in the infrastructure pool";
                type string;
                mandatory true;
            }
        }
    }    

    notification update {
        uses deviceItem;

        leaf change {
            type enumeration {
                enum added;
                enum removed;
            }                
        }        
    }
}
