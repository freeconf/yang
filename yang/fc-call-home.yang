module fc-call-home {
    prefix "home";
    namespace "freeconf.org/fc-call-home";
    description "Configuring connection to a call-home service. Inspired by call-home RFC draft 
      but should be replaced with official implementation eventually.";
    revision 0000-00-00;

    grouping callHome {
        action register {
            input {}
        }

        action unregister {
            input {}
        }

        notification update {
            description "Change in registration status.";
            leaf registered {
                type boolean;
            }
            leaf err {
                description "Last registration error if there was one";
                type string;
            }
        }

        leaf registered {
            description "Success registration";
            config false;
            type boolean;
        }

        leaf deviceId {
            description  "Unique device id within your infrastructure for this device.";
            type string;
        }

        leaf address {
            description "Hostname or IP address of application management system.";
            type string;
        }

        leaf endpoint {
            description "endpoint appended to address to device to register to. e.g. /restconf";
            type string;
        }

        leaf localAddress {
            description "When client is initiating connection to a registration server, this is the network address";
            type string;        
        }

        leaf retryRateMs {
            description "If registration fails, try again after given ms.";
            type int32;
            default 10000;
        }
    }
}
