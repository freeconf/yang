module stocklib {
	namespace "org.freeconf/stock";
	prefix "stock";
    description "management of various objects on C2 library";
	revision 0;

    grouping tls {

        leaf serverName {
            description "Name identified in certificate for this server";
            type string;
        }

        container cert {
            leaf certFile {
                description "PEM encoded certification";
                type string;
            }
            leaf keyFile {
                description "PEM encoded private key used to build certificate";
                type string;
            }
        }

        container ca {
            leaf certFile {
                description "PEM encoded certificate of certificate authority used to sign certificate";
                type string;
            }
        }
    }
}
