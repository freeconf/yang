module restconf {
	namespace "org.freeconf/restconf";
	prefix "restconf";
    import stocklib {
        prefix "stock";
    }
    import call-home {
        prefix "chome";
    }
    
    description "service that implements RESTCONF RFC8040 device protocol";
	revision 0;

    leaf notifyKeepaliveTimeoutMs {
        description "close the connection after N milliseconds of no pings or activity";
        type int32;
        default 30000;
    }

	leaf debug {
	    description "enable debug log messages";
        type boolean;
	    default "false";
    }

    leaf streamCount {
        description "number of open sessions. each session have have many subscriptions";
        type int32;
        config false;
    }

    leaf subscriptionCount {
        description "number of subscriptions across all sessions";
        type int32;
        config false;        
    }

    container web {
        description "web service used by restconf server";

        leaf port {
            description "required port number.  Examples :8010  192.168.1.10:8080";
            type string;
        }

        leaf readTimeout {
            description "timeout in milliseconds to wait for reading data from client";
            type int32;
            default 10000;
        }

        leaf writeTimeout {
            description "timeout in milliseconds for sending data from client";
            type int32;
            default 10000;
        }

        container tls {
            description "required for secure transport";
            uses stock:tls;
        }
    }
    
    container callHome {
        uses chome:callHome;
    }
}
