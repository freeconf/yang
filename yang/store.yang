module store {
    prefix "";
    namespace "";
    revision 0;

    leaf storeDir {
        type string;
    }

    grouping deviceInfo {
        leaf deviceId {
            type string;
        }
        leaf module {
            type string;
        }
    }

    rpc sync {
        description "Exchange configuration between endpoint and server to ensure they are the same.  Takes server's
        configuration over endpoints. Effectively this simply does a push then a pull.  If you'd prefer to
        use the endpoint's configuration over the servers when they conflict, then simply call pullConfig then pushConfig.";

        uses deviceInfo;
    }

    rpc pull {
        description "Merge in endpoints configuration with server's. If a device registers with initial configuration
        different than servers, this will merge the two copies giving preference to servers.";

        uses deviceInfo;
    }

    rpc push {
        description "Merge server's configuration with endpoints.  Only required when you know the endpoint's configuration
        is out of sync with server's.  Useful after a mergeConfig to ensure all of device's configuration is ";

        uses deviceInfo;
    }
}
