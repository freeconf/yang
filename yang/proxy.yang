module proxy {
    prefix "";
    namespace "";
    revision 0;

    list device {
        key "id";
        config "false";
        
        leaf id {
            type string;
        }

        leaf schema {
            type string;
        }

        leaf data {
            type string;
        }

        leaf stream {
            type string;
        }

        leaf remoteAddress {
            type string;
        }

        leaf remotePort {
            type string;
        }

        list module {
            key "name";        

            leaf name {
                type string;
            }

            leaf revision {
                type string;
            }        
        }
    }

    notification deviceUpdate {
        leaf device {
            type string;
        }
        leaf change {
            type enumeration {
                enum added;
                enum removed;
            }                
        }        
    }

    notification moduleUpdate {
        leaf device {
            type string;
        }
        leaf module {
            type string;
        }
        leaf change {
            type enumeration {
                enum added;
                enum removed;
            }                
        }
    }
}
