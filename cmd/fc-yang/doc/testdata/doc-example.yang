module doc-example {
    prefix "";
    namespace "";
    revision 0;

    identity family {
        description "Type of device";
    }

    identity warbler {
        base family;
    }

    list bird {
        key "name";
        leaf name {
            type string;
        }
        leaf family {
            type identityref {
                base family;
            }
        }
        leaf wingSpan {
            description "in cm";
            type int32;
            default "64";
        }
    }

    leaf level {
        type enumeration {
            enum casual;
            enum hobbiest;
            enum birdNerd {
                value 1000;
            }
        }
    }

    choice origin {
        case case0 {
            leaf country {
                type string;
            }
        }
        case case1 {
            leaf planet {
                type string;
            }
            leaf moon {
                type string;
            }
        }
    }

    choice record {
        case audobon {
            container audobon {
                leaf page {
                    type string;
                }
            }            
        }
        case peterson {
            container peterson {
                leaf link {
                    type string;
                }
            }
        }
    }

    action fly {
        input {
            container vector {
                leaf x {
                    type string;
                }
            }
            leaf originalWeight {
                type decimal64;
            }
        }
        output {
            list log {
                leaf length {
                    type int32;
                }
            }
            leaf speed {
                type decimal64;
            }
        }
    }

    notification migration {
        leaf logEntry {
            type string;
        }
        container status {
            leaf energyLevel {
                type int64;
            }
        }
        choice notifChoice {
            leaf choice1 {
                type string;
            }
            leaf choice2 {
                type string;
            }
        }
    }
}
