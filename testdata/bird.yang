module bird {
    prefix "";
    namespace "";
    revision 0;

    list bird {
        key "name";
        leaf name {
            type string;
        }
        leaf wingspan {
            type int32;
        }
        container species {
            leaf name {
                type string;
            }
            leaf class {
                type string;
            }
        }
    }
}
