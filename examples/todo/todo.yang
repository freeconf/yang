module todo {
    namespace "todo";
    prefix "http://conf2.org/todo";
    revision 0;

    list todos {
        key "id";
        leaf id {
            type string;
        }
        leaf status {
            type enumeration {
                enum done;
                enum todo;
            }
            default "todo";
        }
        leaf summary {
            type string;
        }
        leaf description {
            type string;
        }
        leaf-list keywords {
            type string;
        }
        leaf dueDate {
            type int64;
        }
    }
}
