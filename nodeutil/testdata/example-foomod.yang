module example-foomod {

    description "
      This sample comes from RFC on namespacing JSON
        https://datatracker.ietf.org/doc/html/rfc7951
    ";
    
    namespace "http://example.com/foomod";
    prefix "foomod";

    grouping x {
        container top {
            leaf foo {
                type uint8;
            }    
        }
    }
}
