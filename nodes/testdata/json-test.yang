module json-test {
	prefix "t";
	namespace "t";
	contact "c";
	reference "r";
	organization "o";
	revision 0;

	grouping g {
		container metric {
			reference "mr";
			config false;
			leaf v {
				type string;
			}
		}
	}

	list hobbies {
		reference "hr";
		container birding {
			leaf favorite-species {
				type string;
			}
		}

		container hockey {
			leaf favorite-team {
				type string;
			}
		}
		uses g {
			refine metric {
				config false;
			}
		}
	}

	action foo {
		input {
			leaf a {
				type string;
			}
		}
		output {
			leaf b {
				type string;
			}
		}
	}

	notification n {
		leaf-list ll {
			type int32;
			max-elements 10;						
		}
	}
}
