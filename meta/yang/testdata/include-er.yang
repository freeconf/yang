module includer-er {
    prefix "";
    namespace "";
    include include-ee1;
    revision 0;
    include include-ee2 {
        revision 0;
        description "d";
        reference "99";
    }

    leaf x {
        type string;
    }
}
