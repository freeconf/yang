module x {
    prefix "";
    namespace "";
    include one;
    revision 0;
    include two {
        revision 0;
        description "d";
        reference "99";
    }

    leaf x {
        type string;
    }
}
