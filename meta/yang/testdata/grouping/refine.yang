module refine {
    namespace "";
    prefix "";
    revision 0;
    
    grouping x {
        leaf s {
            description "orig";
            type string;
        }
        container t {
            description "orig II";
            leaf u {
                description "orig III";
                type string;
            }
        }
        leaf-list i {
            type int32;
            min-elements 1;
        }
    }

    container a {
        uses x {
            refine s {
                description "refined";                
                default "hello";
                mandatory true;
            }
            refine t/u {
                description "refined II";
                config false;
            }
            refine i {
                min-elements 1;
                max-elements 100;
            }
        }
    }
    container b {
        uses x;
    }
}
