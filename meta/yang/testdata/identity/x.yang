module x {
    prefix "";
    namespace "";
    revision 0;
    import y {
        prefix y;
    }

    identity x;

    identity y {
        description "d";
        reference "r";
        base x;
    }

    identity z {
        base y;
        base x;
        base y:a;
    }

    leaf l {
        type identityref {
            base z;
        }
    }

    leaf l2 {
        type identityref {
            base y:a;
        }
    }
}
