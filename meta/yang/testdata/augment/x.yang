module x {
    prefix "";
    namespace "";
    revision 0;

    container x {
        container y {
            leaf a {
                type string;
            }
        }
    }

    augment x/y {
        description "x";
        leaf b {
            type string;
        }
    }
}
