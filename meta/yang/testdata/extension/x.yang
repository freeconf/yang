module x {
    description "x" {
        custom 5;
    }
    leaf x {
        type string;
    }

    some:ext "z";

    extension ext {
        argument "f" {
            yin-element false;
        }
        description "x";
    }

    extension ext2 {        
    }
}
