module leafref {
    revision 0;

    grouping g {
        leaf x {
            type string;
        }
    }
    grouping g2 {
        list c {
            leaf l {
                type leafref {
                    path "../c/x";
                }
            }
            container c {
                uses g;
            }
        }
    }
    uses g2;
}
